GUDEADS-EPC8210-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }


gadsEPC8210 OBJECT IDENTIFIER 
	-- 1.3.6.1.4.1.28507.29
	::= { gudeads 29 }

-- Notification Types
--

events OBJECT IDENTIFIER 
	-- 1.3.6.1.4.1.28507.29.0
	::= { gadsEPC8210 0 }

-- Scalars and Tables
--

epc8210Objects OBJECT IDENTIFIER 
	-- 1.3.6.1.4.1.28507.29.1
	::= { gadsEPC8210 1 }

epc8210CommonConfig OBJECT IDENTIFIER 
	-- 1.3.6.1.4.1.28507.29.1.1
	::= { epc8210Objects 1 }

epc8210SNMPaccess OBJECT IDENTIFIER 
	-- 1.3.6.1.4.1.28507.29.1.1.1
	::= { epc8210CommonConfig 1 }

epc8210TrapCtrl OBJECT-TYPE
	SYNTAX  Integer32 (0..2)
	MAX-ACCESS read-write
	STATUS  current
	DESCRIPTION
		"0 = off
		1 = Ver. 1
		2 = Ver. 2c"
	-- 1.3.6.1.4.1.28507.29.1.1.1.1
	::= { epc8210SNMPaccess 1 }


epc8210TrapIPTable OBJECT-TYPE
	SYNTAX  SEQUENCE OF Epc8TrapIPEntry
	MAX-ACCESS not-accessible
	STATUS  current
	DESCRIPTION
		"list of all Trap receiver"
	-- 1.3.6.1.4.1.28507.29.1.1.1.2
	::= { epc8210SNMPaccess 2 }


epc8210TrapIPEntry OBJECT-TYPE
	SYNTAX  Epc8TrapIPEntry
	MAX-ACCESS not-accessible
	STATUS  current
	DESCRIPTION
		"an entry containing management
		informations regarding the list of trap
		receivers"
	INDEX {
		epc8210TrapIPIndex }
	-- 1.3.6.1.4.1.28507.29.1.1.1.2.1
	::= { epc8210TrapIPTable 1 }


Epc8TrapIPEntry ::= SEQUENCE {

	epc8210TrapIPIndex Integer32,
	epc8210TrapAddr    OCTET STRING }


epc8210TrapIPIndex OBJECT-TYPE
	SYNTAX  Integer32 (1..8)
	MAX-ACCESS not-accessible
	STATUS  current
	DESCRIPTION
		"A unique value, greater than zero, for each receiver slot."
	-- 1.3.6.1.4.1.28507.29.1.1.1.2.1.1
	::= { epc8210TrapIPEntry 1 }


epc8210TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.29.1.1.1.2.1.2
	::= { epc8210TrapIPEntry 2 }


epc8210DeviceConfig OBJECT IDENTIFIER 
	-- 1.3.6.1.4.1.28507.29.1.2
	::= { epc8210Objects 2 }

epc8210IntActors OBJECT IDENTIFIER 
	-- 1.3.6.1.4.1.28507.29.1.3
	::= { epc8210Objects 3 }

epc8210relayports OBJECT IDENTIFIER 
	-- 1.3.6.1.4.1.28507.29.1.3.1
	::= { epc8210IntActors 1 }

epc8210portNumber OBJECT-TYPE
	SYNTAX  Integer32 (1..8)
	MAX-ACCESS read-only
	STATUS  current
	DESCRIPTION
		"The number of Relay Ports"
	-- 1.3.6.1.4.1.28507.29.1.3.1.1
	::= { epc8210relayports 1 }


-- the Interfaces table
-- The Interfaces table contains information on the entity's
-- interfaces.  Each sub-layer below the internetwork-layer
-- of a network interface is considered to be an interface.

epc8210portTable OBJECT-TYPE
	SYNTAX  SEQUENCE OF Epc8210portEntry
	MAX-ACCESS not-accessible
	STATUS  current
	DESCRIPTION
		"list of all EPC Relay Ports"
	-- 1.3.6.1.4.1.28507.29.1.3.1.2
	::= { epc8210relayports 2 }


epc8210portEntry OBJECT-TYPE
	SYNTAX  Epc8210portEntry
	MAX-ACCESS not-accessible
	STATUS  current
	DESCRIPTION
		"An entry containing management information applicable to a
		particular relay port."
	INDEX {
		epc8210PortIndex }
	-- 1.3.6.1.4.1.28507.29.1.3.1.2.1
	::= { epc8210portTable 1 }


Epc8210portEntry ::= SEQUENCE {

	epc8210PortIndex        Integer32,
	epc8210PortName         OCTET STRING,
	epc8210PortState        INTEGER,
	epc8210PortSwitchCount  Integer32,
	epc8210PortStartupMode  INTEGER,
	epc8210PortStartupDelay Integer32,
	epc8210PortRepowerTime  Integer32 }


epc8210PortIndex OBJECT-TYPE
	SYNTAX  Integer32 (1..8)
	MAX-ACCESS not-accessible
	STATUS  current
	DESCRIPTION
		"A unique value, greater than zero, for each Relay Port."
	-- 1.3.6.1.4.1.28507.29.1.3.1.2.1.1
	::= { epc8210portEntry 1 }


epc8210PortName OBJECT-TYPE
	SYNTAX  OCTET STRING (SIZE (0..15))
	MAX-ACCESS read-only
	STATUS  current
	DESCRIPTION
		"A textual string containing name of a Relay Port."
	-- 1.3.6.1.4.1.28507.29.1.3.1.2.1.2
	::= { epc8210portEntry 2 }


epc8210PortState OBJECT-TYPE
	SYNTAX  INTEGER {
			off(0),
			on(1) }
	MAX-ACCESS read-write
	STATUS  current
	DESCRIPTION
		"current state a Relay Port"
	-- 1.3.6.1.4.1.28507.29.1.3.1.2.1.3
	::= { epc8210portEntry 3 }


epc8210PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.29.1.3.1.2.1.4
	::= { epc8210portEntry 4 }


epc8210PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.29.1.3.1.2.1.5
	::= { epc8210portEntry 5 }


epc8210PortStartupDelay OBJECT-TYPE
	SYNTAX  Integer32
	UNITS
		"seconds"
	MAX-ACCESS read-write
	STATUS  current
	DESCRIPTION
		"Delay in sec for startup action"
	DEFVAL { 0 }
	-- 1.3.6.1.4.1.28507.29.1.3.1.2.1.6
	::= { epc8210portEntry 6 }


epc8210PortRepowerTime OBJECT-TYPE
	SYNTAX  Integer32 (0..65535)
	UNITS
		"seconds"
	MAX-ACCESS read-write
	STATUS  current
	DESCRIPTION
		"Delay in sec for repower port after switching off"
	DEFVAL { 0 }
	-- 1.3.6.1.4.1.28507.29.1.3.1.2.1.7
	::= { epc8210portEntry 7 }


epc8210Buzzer OBJECT-TYPE
	SYNTAX  Integer32 (0..1)
	UNITS
		"0 = Off, 1 = On"
	MAX-ACCESS read-write
	STATUS  current
	DESCRIPTION
		"turn Buzzer on and off"
	-- 1.3.6.1.4.1.28507.29.1.3.10
	::= { epc8210IntActors 10 }


epc8210ExtActors OBJECT IDENTIFIER 
	-- 1.3.6.1.4.1.28507.29.1.4
	::= { epc8210Objects 4 }

epc8210IntSensors OBJECT IDENTIFIER 
	-- 1.3.6.1.4.1.28507.29.1.5
	::= { epc8210Objects 5 }

epc8210PowerChan OBJECT IDENTIFIER 
	-- 1.3.6.1.4.1.28507.29.1.5.1
	::= { epc8210IntSensors 1 }

epc8210ActivePowerChan OBJECT-TYPE
	SYNTAX  Unsigned32 (1)
	MAX-ACCESS read-only
	STATUS  current
	DESCRIPTION
		"Number of suppported Power Channels."
	-- 1.3.6.1.4.1.28507.29.1.5.1.1
	::= { epc8210PowerChan 1 }


epc8210PowerTable OBJECT-TYPE
	SYNTAX  SEQUENCE OF Epc8210PowerEntry
	MAX-ACCESS not-accessible
	STATUS  current
	DESCRIPTION
		"All available Channel Interfaces."
	-- 1.3.6.1.4.1.28507.29.1.5.1.2
	::= { epc8210PowerChan 2 }


epc8210PowerEntry OBJECT-TYPE
	SYNTAX  Epc8210PowerEntry
	MAX-ACCESS not-accessible
	STATUS  current
	DESCRIPTION
		"An entry containing management information
		applicable to a particular Power Channel."
	INDEX {
		epc8210PowerIndex }
	-- 1.3.6.1.4.1.28507.29.1.5.1.2.1
	::= { epc8210PowerTable 1 }


Epc8210PowerEntry ::= SEQUENCE {

	epc8210PowerIndex Integer32,
	epc8210ChanStatus Unsigned32,
	epc8210Current    Unsigned32 }


epc8210PowerIndex OBJECT-TYPE
	SYNTAX  Integer32 (1)
	MAX-ACCESS not-accessible
	STATUS  current
	DESCRIPTION
		"Index of Power Channel entries"
	-- 1.3.6.1.4.1.28507.29.1.5.1.2.1.1
	::= { epc8210PowerEntry 1 }


epc8210ChanStatus OBJECT-TYPE
	SYNTAX  Unsigned32 (0..1)
	MAX-ACCESS read-only
	STATUS  current
	DESCRIPTION
		"0 = data not active, 1 = data valid"
	-- 1.3.6.1.4.1.28507.29.1.5.1.2.1.2
	::= { epc8210PowerEntry 2 }


epc8210Current OBJECT-TYPE
	SYNTAX  Unsigned32
	UNITS
		"mA"
	MAX-ACCESS read-only
	STATUS  current
	DESCRIPTION
		"Actual Current on Power Channel."
	-- 1.3.6.1.4.1.28507.29.1.5.1.2.1.5
	::= { epc8210PowerEntry 5 }


epc8210ExtSensors OBJECT IDENTIFIER 
	-- 1.3.6.1.4.1.28507.29.1.6
	::= { epc8210Objects 6 }

epc8210SensorTable OBJECT-TYPE
	SYNTAX  SEQUENCE OF Epc8210SensorEntry
	MAX-ACCESS not-accessible
	STATUS  current
	DESCRIPTION ""
	-- 1.3.6.1.4.1.28507.29.1.6.1
	::= { epc8210ExtSensors 1 }


epc8210SensorEntry OBJECT-TYPE
	SYNTAX  Epc8210SensorEntry
	MAX-ACCESS not-accessible
	STATUS  current
	DESCRIPTION ""
	INDEX {
		epc8210SensorIndex }
	-- 1.3.6.1.4.1.28507.29.1.6.1.1
	::= { epc8210SensorTable 1 }


Epc8210SensorEntry ::= SEQUENCE {

	epc8210SensorIndex Integer32,
	epc8210TempSensor  Integer32,
	epc8210HygroSensor Integer32,
	epc8210InputSensor INTEGER }


epc8210SensorIndex OBJECT-TYPE
	SYNTAX  Integer32 (1..2)
	MAX-ACCESS not-accessible
	STATUS  current
	DESCRIPTION ""
	-- 1.3.6.1.4.1.28507.29.1.6.1.1.1
	::= { epc8210SensorEntry 1 }


epc8210TempSensor OBJECT-TYPE
	SYNTAX  Integer32
	UNITS
		"0.1 degree Celsius"
	MAX-ACCESS read-only
	STATUS  current
	DESCRIPTION
		"actual temperature,  a value of -9999 indicates
		that data is not available"
	-- 1.3.6.1.4.1.28507.29.1.6.1.1.2
	::= { epc8210SensorEntry 2 }


epc8210HygroSensor OBJECT-TYPE
	SYNTAX  Integer32
	UNITS
		"0.1 percent humidity"
	MAX-ACCESS read-only
	STATUS  current
	DESCRIPTION
		"actual humidity,  a value of -9999 indicates
		that data is not available"
	-- 1.3.6.1.4.1.28507.29.1.6.1.1.3
	::= { epc8210SensorEntry 3 }


epc8210InputSensor OBJECT-TYPE
	SYNTAX  INTEGER {
			off(0),
			on(1) }
	MAX-ACCESS read-only
	STATUS  current
	DESCRIPTION
		"logical state of input sensor"
	-- 1.3.6.1.4.1.28507.29.1.6.1.1.4
	::= { epc8210SensorEntry 4 }


-- Conformance
--

epc8210Conf OBJECT IDENTIFIER 
	-- 1.3.6.1.4.1.28507.29.2
	::= { gadsEPC8210 2 }

-- Groups
--

epc8210Groups OBJECT IDENTIFIER 
	-- 1.3.6.1.4.1.28507.29.2.1
	::= { epc8210Conf 1 }

-- Compliance
--

epc8210Compls OBJECT IDENTIFIER 
	-- 1.3.6.1.4.1.28507.29.2.2
	::= { epc8210Conf 2 }


epc8210SwitchEvtPort1 NOTIFICATION-TYPE
	OBJECTS {
		epc8210PortName,
		epc8210PortState,
		epc8210PortSwitchCount}
	STATUS  current
	DESCRIPTION
		"Event is triggered when a port is switched"
	-- 1.3.6.1.4.1.28507.29.0.1
	::= { events 1 }


epc8210SwitchEvtPort2 NOTIFICATION-TYPE
	OBJECTS {
		epc8210PortName,
		epc8210PortState,
		epc8210PortSwitchCount}
	STATUS  current
	DESCRIPTION
		"Event is triggered when a port is switched"
	-- 1.3.6.1.4.1.28507.29.0.2
	::= { events 2 }


epc8210SwitchEvtPort3 NOTIFICATION-TYPE
	OBJECTS {
		epc8210PortName,
		epc8210PortState,
		epc8210PortSwitchCount}
	STATUS  current
	DESCRIPTION
		"Event is triggered when a port is switched"
	-- 1.3.6.1.4.1.28507.29.0.3
	::= { events 3 }


epc8210SwitchEvtPort4 NOTIFICATION-TYPE
	OBJECTS {
		epc8210PortName,
		epc8210PortState,
		epc8210PortSwitchCount}
	STATUS  current
	DESCRIPTION
		"Event is triggered when a port is switched"
	-- 1.3.6.1.4.1.28507.29.0.4
	::= { events 4 }


epc8210SwitchEvtPort5 NOTIFICATION-TYPE
	OBJECTS {
		epc8210PortName,
		epc8210PortState,
		epc8210PortSwitchCount}
	STATUS  current
	DESCRIPTION
		"Event is triggered when a port is switched"
	-- 1.3.6.1.4.1.28507.29.0.5
	::= { events 5 }


epc8210SwitchEvtPort6 NOTIFICATION-TYPE
	OBJECTS {
		epc8210PortName,
		epc8210PortState,
		epc8210PortSwitchCount}
	STATUS  current
	DESCRIPTION
		"Event is triggered when a port is switched"
	-- 1.3.6.1.4.1.28507.29.0.6
	::= { events 6 }


epc8210SwitchEvtPort7 NOTIFICATION-TYPE
	OBJECTS {
		epc8210PortName,
		epc8210PortState,
		epc8210PortSwitchCount}
	STATUS  current
	DESCRIPTION
		"Event is triggered when a port is switched"
	-- 1.3.6.1.4.1.28507.29.0.7
	::= { events 7 }


epc8210SwitchEvtPort8 NOTIFICATION-TYPE
	OBJECTS {
		epc8210PortName,
		epc8210PortState,
		epc8210PortSwitchCount}
	STATUS  current
	DESCRIPTION
		"Event is triggered when a port is switched"
	-- 1.3.6.1.4.1.28507.29.0.8
	::= { events 8 }


epc8210TempEvtSen1 NOTIFICATION-TYPE
	OBJECTS {
		epc8210TempSensor}
	STATUS  current
	DESCRIPTION
		"temperature limits exceeded"
	-- 1.3.6.1.4.1.28507.29.0.9
	::= { events 9 }


epc8210TempEvtSen2 NOTIFICATION-TYPE
	OBJECTS {
		epc8210TempSensor}
	STATUS  current
	DESCRIPTION
		"temperature limits exceeded"
	-- 1.3.6.1.4.1.28507.29.0.10
	::= { events 10 }


epc8210HygroEvtSen1 NOTIFICATION-TYPE
	OBJECTS {
		epc8210HygroSensor}
	STATUS  current
	DESCRIPTION
		"hygro limits exceeded"
	-- 1.3.6.1.4.1.28507.29.0.11
	::= { events 11 }


epc8210HygroEvtSen2 NOTIFICATION-TYPE
	OBJECTS {
		epc8210HygroSensor}
	STATUS  current
	DESCRIPTION
		"hygro limits exceeded"
	-- 1.3.6.1.4.1.28507.29.0.12
	::= { events 12 }


epc8210InputEvtSen1 NOTIFICATION-TYPE
	OBJECTS {
		epc8210InputSensor}
	STATUS  current
	DESCRIPTION
		"change of logical input sensor state"
	-- 1.3.6.1.4.1.28507.29.0.13
	::= { events 13 }


epc8210InputEvtSen2 NOTIFICATION-TYPE
	OBJECTS {
		epc8210InputSensor}
	STATUS  current
	DESCRIPTION
		"change of logical input sensor state"
	-- 1.3.6.1.4.1.28507.29.0.14
	::= { events 14 }

epc8210BasicGroup OBJECT-GROUP
	OBJECTS {
		epc8210TrapCtrl,
		epc8210TrapAddr,
		epc8210portNumber,
		epc8210PortName,
		epc8210PortState,
		epc8210PortSwitchCount,
		epc8210PortStartupMode,
		epc8210PortStartupDelay,
		epc8210PortRepowerTime,
		epc8210ActivePowerChan,
		epc8210ChanStatus,
		epc8210Current,
		epc8210TempSensor,
		epc8210HygroSensor,
		epc8210InputSensor,
		epc8210Buzzer }
	STATUS  current
	DESCRIPTION
		"Basic objects."
	-- 1.3.6.1.4.1.28507.29.2.1.1
	::= { epc8210Groups 1 }

epc8210NotificationGroup NOTIFICATION-GROUP
	NOTIFICATIONS {
		epc8210SwitchEvtPort1,
		epc8210SwitchEvtPort2,
		epc8210SwitchEvtPort3,
		epc8210SwitchEvtPort4,
		epc8210SwitchEvtPort5,
		epc8210SwitchEvtPort6,
		epc8210SwitchEvtPort7,
		epc8210SwitchEvtPort8,
		epc8210TempEvtSen1,
		epc8210HygroEvtSen1,
		epc8210TempEvtSen2,
		epc8210HygroEvtSen2,
		epc8210InputEvtSen1,
		epc8210InputEvtSen2 }
	STATUS  current
	DESCRIPTION
		""
	-- 1.3.6.1.4.1.28507.29.2.1.2
	::= { epc8210Groups 2 }

END
